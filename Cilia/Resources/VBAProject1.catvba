Attribute VB_Name = "Module1"
Sub CATMain()

    Dim i As Integer
    Dim prt As Part
    Set prt = CATIA.ActiveDocument.Part
    Dim offset As Length
    Set offset = prt.Parameters.GetItem("Offset")
    Dim vwr As Viewer
    Set vwr = CATIA.ActiveWindow.ActiveViewer
    For i = 0 To -120 Step -2
        offset.Value = i
        prt.Update
        vwr.CaptureToFile catCaptureFormatBMP, "C:\Users\to101757\Documents\92.VB.Net\Cilia\trunk\Cilia\Resources\Screens\" + Str(i) + ".bmp"
    Next


End Sub

Attribute VB_Name = "Module2"
Sub CATMain()

End Sub
